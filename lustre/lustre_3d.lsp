;;; LUSTRE3D - construit le lustre cascade dans AutoCAD avec la suspension fournie.
;;; Utilisation : APPLOAD -> lustre_3d.lsp, puis taper LUSTRE3D dans un dessin vide (unites mm).
;;; Le fichier suspension5.dwg est cherche dans le dossier de ce .lsp, sinon il est demande.
;;; La suspension est accrochee par le CENTRE DE SON SOMMET au bout de chaque fil.
;;; Mettre *LUSTRE-FLIP* a T si la suspension apparait la tete en bas.
(vl-load-com)
(setq *LUSTRE-FLIP* nil)
(setq *LUSTRE-DIR* (if (findfile "lustre_3d.lsp") (vl-filename-directory (findfile "lustre_3d.lsp")) ""))
;;; (repere x y fil) en mm - origine coin bas-gauche du plateau, fil = plateau -> haut de la suspension
(setq *LUSTRE-PTS* '(
("A01" 100.0 2300.0 3390.0)
("A02" 300.0 2300.0 1540.0)
("A03" 500.0 2300.0 2760.0)
("A04" 700.0 2300.0 2170.0)
("A05" 900.0 2300.0 4570.0)
("A06" 1100.0 2300.0 1490.0)
("A07" 1300.0 2300.0 4000.0)
("A08" 1500.0 2300.0 1540.0)
("A09" 1700.0 2300.0 3290.0)
("A10" 1900.0 2300.0 4410.0)
("A11" 2100.0 2300.0 2810.0)
("A12" 2300.0 2300.0 4380.0)
("A13" 2500.0 2300.0 2780.0)
("A14" 2700.0 2300.0 1120.0)
("A15" 2900.0 2300.0 3270.0)
("B01" 200.0 2200.0 2340.0)
("B02" 400.0 2200.0 4330.0)
("B03" 600.0 2200.0 1380.0)
("B04" 800.0 2200.0 3450.0)
("B05" 1000.0 2200.0 2710.0)
("B06" 1200.0 2200.0 5110.0)
("B07" 1400.0 2200.0 3210.0)
("B08" 1600.0 2200.0 2410.0)
("B09" 1800.0 2200.0 1390.0)
("B10" 2000.0 2200.0 3550.0)
("B11" 2200.0 2200.0 2080.0)
("B12" 2400.0 2200.0 1440.0)
("B13" 2600.0 2200.0 3830.0)
("B14" 2800.0 2200.0 2260.0)
("C01" 100.0 2100.0 3970.0)
("C02" 300.0 2100.0 3000.0)
("C03" 500.0 2100.0 3600.0)
("C04" 700.0 2100.0 4270.0)
("C05" 900.0 2100.0 1850.0)
("C06" 1100.0 2100.0 3480.0)
("C07" 1300.0 2100.0 2510.0)
("C08" 1500.0 2100.0 4690.0)
("C09" 1700.0 2100.0 5290.0)
("C10" 1900.0 2100.0 2190.0)
("C11" 2100.0 2100.0 1330.0)
("C12" 2300.0 2100.0 3800.0)
("C13" 2500.0 2100.0 4860.0)
("C14" 2700.0 2100.0 1630.0)
("C15" 2900.0 2100.0 4340.0)
("D01" 200.0 2000.0 4790.0)
("D02" 400.0 2000.0 2030.0)
("D03" 600.0 2000.0 2810.0)
("D04" 800.0 2000.0 5080.0)
("D05" 1000.0 2000.0 4290.0)
("D06" 1200.0 2000.0 1090.0)
("D07" 1400.0 2000.0 1800.0)
("D08" 1600.0 2000.0 3770.0)
("D09" 1800.0 2000.0 2950.0)
("D10" 2000.0 2000.0 4030.0)
("D11" 2200.0 2000.0 4700.0)
("D12" 2400.0 2000.0 3130.0)
("D13" 2600.0 2000.0 2490.0)
("D14" 2800.0 2000.0 3220.0)
("E01" 100.0 1900.0 1990.0)
("E02" 300.0 1900.0 1220.0)
("E03" 500.0 1900.0 4760.0)
("E04" 700.0 1900.0 1210.0)
("E05" 900.0 1900.0 2850.0)
("E06" 1100.0 1900.0 5220.0)
("E07" 1300.0 1900.0 4200.0)
("E08" 1500.0 1900.0 5650.0)
("E09" 1700.0 1900.0 1470.0)
("E10" 1900.0 1900.0 4680.0)
("E11" 2100.0 1900.0 2950.0)
("E12" 2300.0 1900.0 2240.0)
("E13" 2500.0 1900.0 1720.0)
("E14" 2700.0 1900.0 3830.0)
("E15" 2900.0 1900.0 2110.0)
("F01" 200.0 1800.0 2980.0)
("F02" 400.0 1800.0 3800.0)
("F03" 600.0 1800.0 1950.0)
("F04" 800.0 1800.0 3520.0)
("F05" 1000.0 1800.0 1640.0)
("F06" 1200.0 1800.0 3340.0)
("F07" 1400.0 1800.0 2620.0)
("F08" 1600.0 1800.0 4520.0)
("F09" 1800.0 1800.0 5530.0)
("F10" 2000.0 1800.0 1910.0)
("F11" 2200.0 1800.0 5530.0)
("F12" 2400.0 1800.0 1010.0)
("F13" 2600.0 1800.0 4660.0)
("F14" 2800.0 1800.0 1260.0)
("G01" 100.0 1700.0 3730.0)
("G02" 300.0 1700.0 2290.0)
("G03" 500.0 1700.0 3040.0)
("G04" 700.0 1700.0 5010.0)
("G05" 900.0 1700.0 4190.0)
("G06" 1100.0 1700.0 2420.0)
("G07" 1300.0 1700.0 1020.0)
("G08" 1500.0 1700.0 1810.0)
("G09" 1700.0 1700.0 2450.0)
("G10" 1900.0 1700.0 3310.0)
("G11" 2100.0 1700.0 4010.0)
("G12" 2300.0 1700.0 4770.0)
("G13" 2500.0 1700.0 3350.0)
("G14" 2700.0 1700.0 2650.0)
("G15" 2900.0 1700.0 4400.0)
("H01" 200.0 1600.0 1450.0)
("H02" 400.0 1600.0 4860.0)
("H03" 600.0 1600.0 4160.0)
("H04" 800.0 1600.0 2340.0)
("H05" 1000.0 1600.0 5660.0)
("H06" 1200.0 1600.0 4180.0)
("H07" 1400.0 1600.0 5000.0)
("H08" 1600.0 1600.0 3130.0)
("H09" 1800.0 1600.0 3990.0)
("H10" 2000.0 1600.0 2670.0)
("H11" 2200.0 1600.0 1320.0)
("H12" 2400.0 1600.0 2410.0)
("H13" 2600.0 1600.0 1780.0)
("H14" 2800.0 1600.0 3440.0)
("I01" 100.0 1500.0 4660.0)
("I02" 300.0 1500.0 3810.0)
("I03" 500.0 1500.0 1610.0)
("I04" 700.0 1500.0 5620.0)
("I05" 900.0 1500.0 3310.0)
("I06" 1100.0 1500.0 1750.0)
("I07" 1300.0 1500.0 5810.0)
("I08" 1500.0 1500.0 3910.0)
("I09" 1700.0 1500.0 1120.0)
("I10" 1900.0 1500.0 5110.0)
("I11" 2100.0 1500.0 2030.0)
("I12" 2300.0 1500.0 3890.0)
("I13" 2500.0 1500.0 5680.0)
("I14" 2700.0 1500.0 4870.0)
("I15" 2900.0 1500.0 2000.0)
("J01" 200.0 1400.0 3210.0)
("J02" 400.0 1400.0 2530.0)
("J03" 600.0 1400.0 3230.0)
("J04" 800.0 1400.0 4160.0)
("J05" 1000.0 1400.0 5010.0)
("J06" 1200.0 1400.0 2610.0)
("J07" 1400.0 1400.0 1470.0)
("J08" 1600.0 1400.0 5480.0)
("J09" 1800.0 1400.0 1930.0)
("J10" 2000.0 1400.0 4400.0)
("J11" 2200.0 1400.0 3010.0)
("J12" 2400.0 1400.0 4760.0)
("J13" 2600.0 1400.0 3980.0)
("J14" 2800.0 1400.0 2780.0)
("K01" 100.0 1300.0 2500.0)
("K02" 300.0 1300.0 5310.0)
("K03" 500.0 1300.0 4310.0)
("K04" 700.0 1300.0 2260.0)
("K05" 900.0 1300.0 1250.0)
("K06" 1100.0 1300.0 4170.0)
("K07" 1300.0 1300.0 4940.0)
("K08" 1500.0 1300.0 2400.0)
("K09" 1700.0 1300.0 4570.0)
("K10" 1900.0 1300.0 3160.0)
("K11" 2100.0 1300.0 5940.0)
("K12" 2300.0 1300.0 1300.0)
("K13" 2500.0 1300.0 2280.0)
("K14" 2700.0 1300.0 1540.0)
("K15" 2900.0 1300.0 3840.0)
("L01" 200.0 1200.0 4310.0)
("L02" 400.0 1200.0 1710.0)
("L03" 600.0 1200.0 1050.0)
("L04" 800.0 1200.0 5910.0)
("L05" 1000.0 1200.0 2100.0)
("L06" 1200.0 1200.0 3340.0)
("L07" 1400.0 1200.0 4260.0)
("L08" 1600.0 1200.0 3420.0)
("L09" 1800.0 1200.0 2460.0)
("L10" 2000.0 1200.0 5150.0)
("L11" 2200.0 1200.0 3940.0)
("L12" 2400.0 1200.0 5650.0)
("L13" 2600.0 1200.0 3180.0)
("L14" 2800.0 1200.0 4650.0)
("M01" 100.0 1100.0 1560.0)
("M02" 300.0 1100.0 3520.0)
("M03" 500.0 1100.0 3100.0)
("M04" 700.0 1100.0 4980.0)
("M05" 900.0 1100.0 3260.0)
("M06" 1100.0 1100.0 5300.0)
("M07" 1300.0 1100.0 1400.0)
("M08" 1500.0 1100.0 5380.0)
("M09" 1700.0 1100.0 1560.0)
("M10" 1900.0 1100.0 3790.0)
("M11" 2100.0 1100.0 1950.0)
("M12" 2300.0 1100.0 4850.0)
("M13" 2500.0 1100.0 4120.0)
("M14" 2700.0 1100.0 5520.0)
("M15" 2900.0 1100.0 2870.0)
("N01" 200.0 1000.0 5280.0)
("N02" 400.0 1000.0 2400.0)
("N03" 600.0 1000.0 4120.0)
("N04" 800.0 1000.0 1360.0)
("N05" 1000.0 1000.0 4400.0)
("N06" 1200.0 1000.0 6170.0)
("N07" 1400.0 1000.0 2150.0)
("N08" 1600.0 1000.0 6260.0)
("N09" 1800.0 1000.0 5350.0)
("N10" 2000.0 1000.0 4500.0)
("N11" 2200.0 1000.0 3260.0)
("N12" 2400.0 1000.0 1180.0)
("N13" 2600.0 1000.0 2100.0)
("N14" 2800.0 1000.0 1370.0)
("O01" 100.0 900.0 3160.0)
("O02" 300.0 900.0 4490.0)
("O03" 500.0 900.0 1690.0)
("O04" 700.0 900.0 2680.0)
("O05" 900.0 900.0 1980.0)
("O06" 1100.0 900.0 3630.0)
("O07" 1300.0 900.0 2850.0)
("O08" 1500.0 900.0 3570.0)
("O09" 1700.0 900.0 2440.0)
("O10" 1900.0 900.0 3070.0)
("O11" 2100.0 900.0 5700.0)
("O12" 2300.0 900.0 2530.0)
("O13" 2500.0 900.0 3460.0)
("O14" 2700.0 900.0 4550.0)
("O15" 2900.0 900.0 2100.0)
("P01" 200.0 800.0 2400.0)
("P02" 400.0 800.0 3680.0)
("P03" 600.0 800.0 4820.0)
("P04" 800.0 800.0 3590.0)
("P05" 1000.0 800.0 2740.0)
("P06" 1200.0 800.0 5100.0)
("P07" 1400.0 800.0 1170.0)
("P08" 1600.0 800.0 4450.0)
("P09" 1800.0 800.0 1290.0)
("P10" 2000.0 800.0 2120.0)
("P11" 2200.0 800.0 1580.0)
("P12" 2400.0 800.0 4180.0)
("P13" 2600.0 800.0 2770.0)
("P14" 2800.0 800.0 3520.0)
("Q01" 100.0 700.0 4000.0)
("Q02" 300.0 700.0 1110.0)
("Q03" 500.0 700.0 2970.0)
("Q04" 700.0 700.0 1060.0)
("Q05" 900.0 700.0 4670.0)
("Q06" 1100.0 700.0 1470.0)
("Q07" 1300.0 700.0 4270.0)
("Q08" 1500.0 700.0 1870.0)
("Q09" 1700.0 700.0 5330.0)
("Q10" 1900.0 700.0 4460.0)
("Q11" 2100.0 700.0 3680.0)
("Q12" 2300.0 700.0 5160.0)
("Q13" 2500.0 700.0 1780.0)
("Q14" 2700.0 700.0 1070.0)
("Q15" 2900.0 700.0 4610.0)
("R01" 200.0 600.0 4790.0)
("R02" 400.0 600.0 1820.0)
("R03" 600.0 600.0 5430.0)
("R04" 800.0 600.0 1910.0)
("R05" 1000.0 600.0 5610.0)
("R06" 1200.0 600.0 3460.0)
("R07" 1400.0 600.0 2470.0)
("R08" 1600.0 600.0 3440.0)
("R09" 1800.0 600.0 2320.0)
("R10" 2000.0 600.0 5310.0)
("R11" 2200.0 600.0 2640.0)
("R12" 2400.0 600.0 3430.0)
("R13" 2600.0 600.0 4970.0)
("R14" 2800.0 600.0 2020.0)
("S01" 100.0 500.0 2660.0)
("S02" 300.0 500.0 3410.0)
("S03" 500.0 500.0 4160.0)
("S04" 700.0 500.0 2660.0)
("S05" 900.0 500.0 3770.0)
("S06" 1100.0 500.0 2150.0)
("S07" 1300.0 500.0 5300.0)
("S08" 1500.0 500.0 4440.0)
("S09" 1700.0 500.0 1340.0)
("S10" 1900.0 500.0 3130.0)
("S11" 2100.0 500.0 1190.0)
("S12" 2300.0 500.0 4270.0)
("S13" 2500.0 500.0 2370.0)
("S14" 2700.0 500.0 3070.0)
("S15" 2900.0 500.0 3650.0)
("T01" 200.0 400.0 1750.0)
("T02" 400.0 400.0 2570.0)
("T03" 600.0 400.0 1180.0)
("T04" 800.0 400.0 4520.0)
("T05" 1000.0 400.0 2950.0)
("T06" 1200.0 400.0 4340.0)
("T07" 1400.0 400.0 1490.0)
("T08" 1600.0 400.0 5380.0)
("T09" 1800.0 400.0 4600.0)
("T10" 2000.0 400.0 3910.0)
("T11" 2200.0 400.0 2000.0)
("T12" 2400.0 400.0 1030.0)
("T13" 2600.0 400.0 3980.0)
("T14" 2800.0 400.0 4580.0)
("U01" 100.0 300.0 3800.0)
("U02" 300.0 300.0 1110.0)
("U03" 500.0 300.0 4890.0)
("U04" 700.0 300.0 3520.0)
("U05" 900.0 300.0 5230.0)
("U06" 1100.0 300.0 1380.0)
("U07" 1300.0 300.0 2720.0)
("U08" 1500.0 300.0 3340.0)
("U09" 1700.0 300.0 2710.0)
("U10" 1900.0 300.0 2050.0)
("U11" 2100.0 300.0 5020.0)
("U12" 2300.0 300.0 3470.0)
("U13" 2500.0 300.0 4960.0)
("U14" 2700.0 300.0 1530.0)
("U15" 2900.0 300.0 2600.0)
("V01" 200.0 200.0 4660.0)
("V02" 400.0 200.0 3840.0)
("V03" 600.0 200.0 2830.0)
("V04" 800.0 200.0 1650.0)
("V05" 1000.0 200.0 3890.0)
("V06" 1200.0 200.0 5020.0)
("V07" 1400.0 200.0 4040.0)
("V08" 1600.0 200.0 1970.0)
("V09" 1800.0 200.0 1240.0)
("V10" 2000.0 200.0 3130.0)
("V11" 2200.0 200.0 2570.0)
("V12" 2400.0 200.0 1610.0)
("V13" 2600.0 200.0 2410.0)
("V14" 2800.0 200.0 3350.0)
("W01" 100.0 100.0 2350.0)
("W02" 300.0 100.0 2980.0)
("W03" 500.0 100.0 1880.0)
("W04" 700.0 100.0 4190.0)
("W05" 900.0 100.0 2310.0)
("W06" 1100.0 100.0 3130.0)
("W07" 1300.0 100.0 1880.0)
("W08" 1500.0 100.0 4850.0)
("W09" 1700.0 100.0 3660.0)
("W10" 1900.0 100.0 4340.0)
("W11" 2100.0 100.0 1510.0)
("W12" 2300.0 100.0 4140.0)
("W13" 2500.0 100.0 3230.0)
("W14" 2700.0 100.0 4170.0)
("W15" 2900.0 100.0 1930.0)
))

(defun lustre:bbox (obj / mn mx)
  (vla-GetBoundingBox obj 'mn 'mx)
  (list (vlax-safearray->list mn) (vlax-safearray->list mx)))

(defun lustre:layer (name col / lay)
  (setq lay (vla-Add (vla-get-Layers (vla-get-ActiveDocument (vlax-get-acad-object))) name))
  (vla-put-Color lay col) name)

(defun c:LUSTRE3D (/ doc ms path ref bb ext h s top n line box base obj)
  (setq doc (vla-get-ActiveDocument (vlax-get-acad-object))
        ms  (vla-get-ModelSpace doc))
  (setq path (findfile (strcat *LUSTRE-DIR* "\\suspension5.dwg")))
  (if (not path) (setq path (findfile "suspension5.dwg")))
  (if (not path) (setq path (getfiled "Choisir le fichier de la suspension" "" "dwg" 0)))
  (if (not path) (progn (princ "\nAucune suspension choisie.") (exit)))
  (setvar "INSUNITS" 4)
  (lustre:layer "PLATEAU" 8) (lustre:layer "FILS" 9) (lustre:layer "SUSPENSIONS" 0)
  ;; 1. Gabarit : insertion du DWG comme bloc, mise a la verticale et a l'echelle
  (setq ref (vla-InsertBlock ms (vlax-3d-point 0 0 0) path 1.0 1.0 1.0 0.0))
  (setq bb (lustre:bbox ref)
        ext (mapcar '- (cadr bb) (car bb)))
  (cond ((and (> (cadr ext) (caddr ext)) (> (cadr ext) (car ext)))
         (vla-Rotate3D ref (vlax-3d-point 0 0 0) (vlax-3d-point 1 0 0) (/ pi 2)))
        ((and (> (car ext) (caddr ext)) (> (car ext) (cadr ext)))
         (vla-Rotate3D ref (vlax-3d-point 0 0 0) (vlax-3d-point 0 1 0) (/ pi 2))))
  (if *LUSTRE-FLIP* (vla-Rotate3D ref (vlax-3d-point 0 0 0) (vlax-3d-point 1 0 0) pi))
  (setq bb (lustre:bbox ref) h (- (caddr (cadr bb)) (caddr (car bb))))
  ;; detection des unites du fichier suspension (hauteur attendue 240 mm)
  (setq s (cond ((and (> h 150.0) (< h 400.0)) 1.0)
                ((and (> h 15.0) (< h 40.0)) 10.0)
                ((and (> h 1.5) (< h 4.0)) 100.0)
                ((and (> h 0.15) (< h 0.4)) 1000.0)
                (T (/ 240.0 h))))
  (if (/= s 1.0) (vla-ScaleEntity ref (vlax-3d-point 0 0 0) s))
  (setq bb (lustre:bbox ref)
        top (list (/ (+ (car (car bb)) (car (cadr bb))) 2.0)
                  (/ (+ (cadr (car bb)) (cadr (cadr bb))) 2.0)
                  (caddr (cadr bb))))
  (princ (strcat "\nSuspension : hauteur " (rtos (* h s) 2 1) " mm (echelle x" (rtos s 2 0) ")"))
  ;; 2. Plateau
  (setq box (vla-AddBox ms (vlax-3d-point (/ 3000.0 2.0) (/ 2400.0 2.0) (/ 30.0 2.0)) 3000.0 2400.0 30.0))
  (vla-put-Layer box "PLATEAU")
  ;; 3. Fils + suspensions
  (setq n 0)
  (foreach p *LUSTRE-PTS*
    (setq base (list (cadr p) (caddr p) (- (cadddr p))))
    (setq line (vla-AddLine ms (vlax-3d-point (cadr p) (caddr p) 0.0) (vlax-3d-point base)))
    (vla-put-Layer line "FILS")
    (setq obj (vla-Copy ref))
    (vla-Move obj (vlax-3d-point top) (vlax-3d-point base))
    (vla-put-Layer obj "SUSPENSIONS")
    (setq n (1+ n)))
  (vla-Delete ref)
  (command "_.-VIEW" "_SEISO")
  (command "_.ZOOM" "_E")
  (command "_.VSCURRENT" "_R")
  (princ (strcat "\n" (itoa n) " suspensions placees. Enregistrer avec ENREGSOUS au format DWG."))
  (princ))
(princ "\nTaper LUSTRE3D pour construire le lustre.")
(princ)
